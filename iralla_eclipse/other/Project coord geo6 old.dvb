Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
Public Sub Main()

    'find the matches geographicales coordinates with the autocad coordinates:
    Dim coord() As Double
    coord = GetCoordinatesReferences() 'coord(3,1) = ((lat1, lng1) , (x1, y1) , (lat2, lng2) , (x2, y2))
    
    Dim lat1 As Double
    Dim lng1 As Double
    Dim x1 As Double
    Dim y1 As Double
    Dim lat2 As Double
    Dim lng2 As Double
    Dim x2 As Double
    Dim y2 As Double
    lat1 = coord(0, 0)
    lng1 = coord(0, 1)
    x1 = coord(1, 0)
    y1 = coord(1, 1)
    lat2 = coord(2, 0)
    lng2 = coord(2, 1)
    x2 = coord(3, 0)
    y2 = coord(3, 1)
    
    'found the geometric transformation:
    t = GetGeoTransformation(coord)
    Dim coef As Double
    Dim rot As Double
    coef = t(0)
    rot = t(1)
    
    'select the polylines to add as bus line:
    GetSelectionOnScreen
    Dim sset As AcadSelectionSet
    Set sset = ThisDrawing.SelectionSets.Item("Polylines")
    
    'write xml file with the datas:
    'root -> layer -> polylines -> vertex
    
    'create the temporary file:
    Set fs = CreateObject("Scripting.FileSystemObject")
    Set xmlFile = fs.CreateTextFile("D:\projet guayaquil\autocad et vba\test visual basic\temporary.xml", True)

    xmlFile.WriteLine ("<?xml version='1.0' encoding='UTF-8'?>")
    
    'write root tag
    xmlFile.WriteLine ("<ROOT>")
    
    'write origine:
    xmlFile.WriteLine ("<O lat='" & lat1 & "' lng='" & lng1 & "'/>")

    Dim coordinates() As Double
    Dim i As Integer
    Dim j As Integer
    Dim LayersName(0 To 200) As String
    Dim XmlLayers(0 To 200) As String
    Dim indiceLayer As Integer
    indiceLayer = 0
    Dim Paradas()
    Dim indiceParadas As Integer
    indiceParadas = 0
    Dim nbrOfLayer As Integer
    nbrOfLayer = 0
    Dim vertexList() As Double
    Dim color As AcadAcCmColor
    Dim rgbColor
    Dim id As Integer
    id = 0
    'Set color = New AcadAcCmColor
    
    'extract the bus stop
    Dim rutaName As String
    ReDim paradaNumberList(3) As Variant  'rutaName ,number value, x, y
    ReDim paradaTxtList(3) As Variant     'rutaName ,texte value, x, y
    Dim paradaCoord(2) As Double
    Dim indiceParadasNum As Integer
    indiceParadasNum = 0
    Dim indiceParadasTxt As Integer
    indiceParadasTxt = 0
    
    For Each Item In sset
        'test if item is a polyline:
        If Item.ObjectName = "AcDbPolyline" Then

                coordinates() = Item.coordinates
                If UBound(coordinates) <> LBound(coordinates) Then
                    
                    'verification if the layer item exist or not:
                    indiceLayer = 0
                    'if it s the first layer:
                    If nbrOfLayer = 0 Then
                        'write in XmlLayer the L tag:
                        XmlLayers(0) = "<L name='" & Item.Layer & "'>"
                        'memorise the layer name:
                        LayersName(0) = Item.Layer
                        nbrOfLayer = nbrOfLayer + 1
                    'else
                    Else
                        'search if the layer item is a new one:
                        For Each LayerName In LayersName
                            If LayerName = Item.Layer Then
                                Exit For
                            ElseIf LayerName = "" Then
                                LayersName(indiceLayer) = Item.Layer
                                XmlLayers(indiceLayer) = "<L name='" & Item.Layer & "'>"
                                nbrOfLayer = nbrOfLayer + 1
                                Exit For
                            End If
                            indiceLayer = indiceLayer + 1
                        Next
                    End If
                    
                    ReDim vertexList((UBound(coordinates) - LBound(coordinates) - 1) / 2, 1)
                    
                    j = 0
                    'extract coordinates, convert them to geograficals coordinates and saved them in vertexList():
                    For i = LBound(coordinates) To UBound(coordinates) - 1 Step 2
                        
                        'conversion to polar coordinates:
                        coordPol = cartesianToPolar(coordinates(i) - x1, coordinates(i + 1) - y1)
                        
                        'conversion to geografical coordinates:
                        alphaGeo = coordPol(1) + rot
                        rGeo = coef * coordPol(0)
                        
                        vertexList(j, 0) = Round(rGeo * Sin(alphaGeo), 6)
                        vertexList(j, 1) = Round(rGeo * Cos(alphaGeo), 6)
                        j = j + 1
                    Next
                    
                    'determinate if the polyline is an Arrow
                    Dim isArrow As Boolean
                    isArrow = False
                    
                    Dim lengthOfPolyline As Integer
                    lengthOfPolyline = UBound(vertexList) - LBound(vertexList)
                    If 4 < lengthOfPolyline And lengthOfPolyline < 20 Then
                      If ((((vertexList(1, 0) - vertexList(5, 0)) < 2) And ((vertexList(1, 1) - vertexList(5, 1)) < 2)) _
                      Or (((vertexList(lengthOfPolyline, 0) - vertexList(lengthOfPolyline - 4, 0)) < 2) And ((vertexList(lengthOfPolyline, 1) - vertexList(lengthOfPolyline - 4, 1)) < 2))) Then
                        isArrow = True
                      End If
                    End If
                    
                    If isArrow = False Then
                        'write polyline tag and its id:
                        XmlLayers(indiceLayer) = XmlLayers(indiceLayer) & "<P id='" & id & "'>"
                        id = id + 1
                    Else
                        'write arrow tag
                        XmlLayers(indiceLayer) = XmlLayers(indiceLayer) & "<A>"
                    End If
                    
                                          
                    'find the color of the polyline:
                    Set color = Item.TrueColor
                    
                    Select Case color.ColorIndex
                        Case acByBlock
                        
                        Case acByLayer
                            rgbColor = getLayerRgb(Item)
                        Case acRed
                        
                        Case acYellow
                        
                        Case acCyan
                        
                        Case acBlue
                        
                        Case acMagenta
                        
                        Case acWhite
                        
                    End Select
                    
                    'write the color:
                        XmlLayers(indiceLayer) = XmlLayers(indiceLayer) _
                                                & "<C value='" & rgbColor & "'/>"
                     
                    'write all the vertex:
                    For i = 0 To j - 1
                        XmlLayers(indiceLayer) = XmlLayers(indiceLayer) _
                                            & "<V lat='" & vertexList(i, 0) & "' lng='" & vertexList(i, 1) & "'/>"
                    Next
                    
                    If isArrow = False Then
                        'write polyline end tag
                        XmlLayers(indiceLayer) = XmlLayers(indiceLayer) & "</P>"
                    Else
                        'write arrow end tag
                        XmlLayers(indiceLayer) = XmlLayers(indiceLayer) & "</A>"
                    End If
                
                End If

        End If
        
        If Item.ObjectName = "AcDbText" And Item.Layer Like "Paradas*" Then
        
            'name of the layer:
            rutaName = Mid$(Item.Layer, 9)
            
            coordinates() = Item.TextAlignmentPoint
            
            'conversion of coordinates:
            'conversion to polar coordinates:
            coordPol = cartesianToPolar(coordinates(0) - x1, coordinates(1) - y1)
            'conversion to geografical coordinates:
            alphaGeo = coordPol(1) + rot
            rGeo = coef * coordPol(0)
            
            paradaCoord(0) = Round(rGeo * Sin(alphaGeo), 6)
            paradaCoord(1) = Round(rGeo * Cos(alphaGeo), 6)
            
            'value of the string:
            If IsNumeric(Item.TextString) Then
                ReDim Preserve paradaNumberList(indiceParadasNum + 3)
                paradaNumberList(indiceParadasNum) = rutaName
                paradaNumberList(indiceParadasNum + 1) = Item.TextString
                paradaNumberList(indiceParadasNum + 2) = paradaCoord(0)
                paradaNumberList(indiceParadasNum + 3) = paradaCoord(1)
                indiceParadasNum = indiceParadasNum + 4
            Else
                ReDim Preserve paradaTxtList(indiceParadasTxt + 3)
                paradaTxtList(indiceParadasTxt) = rutaName
                paradaTxtList(indiceParadasTxt + 1) = Item.TextString
                paradaTxtList(indiceParadasTxt + 2) = paradaCoord(0)
                paradaTxtList(indiceParadasTxt + 3) = paradaCoord(1)
                indiceParadasTxt = indiceParadasTxt + 4
            End If
            
        End If
        
    Next
    
    'link the number with the name of bus stop
    Dim k As Integer
    Dim x As Double
    Dim y As Double
    Dim coordNum(2) As Double
    Dim coordTxt(2) As Double
    Dim distance As Double
    Dim indexFound As Integer
    
    ReDim indiceOfOpenedLayers(0) As Integer
    indiceOfOpenedLayers(0) = -1
    Dim indiceOfindiceOfOpenedLayers
    indiceOfindiceOfOpenedLayers = 0
    Dim LayerOpened As Boolean
    Dim currentLayer
    LayerOpened = False
    
    indiceParadasNum = indiceParadasNum - 4
    indiceParadasTxt = indiceParadasTxt - 4
    
    For i = 0 To indiceParadasNum Step 4
        
        coordNum(0) = paradaNumberList(i + 2)
        coordNum(1) = paradaNumberList(i + 3)
    
        distance = 1000000
        For j = 0 To indiceParadasTxt Step 4
        
            If paradaTxtList(j) = paradaNumberList(i) Then
            
                coordTxt(0) = paradaTxtList(j + 2)
                coordTxt(1) = paradaTxtList(j + 3)
        
                x = coordTxt(0) - coordNum(0)
                y = coordTxt(1) - coordNum(1)
        
                If Sqr(x * x + y * y) < distance Then
                    distance = Sqr(x * x + y * y)
                    indexFound = j
                End If
                
            End If
            
        Next
    
        'record the vertex and name of the parada:
        paradaNumberList(i + 1) = "<V lat='" & paradaNumberList(i + 2) & "' lng='" & paradaNumberList(i + 3) _
                                  & "' n ='" & paradaNumberList(i + 1) & " " & paradaTxtList(indexFound + 1) & "'/>"
       '  paradaNumberList(i + 1) = "<V lat='" & paradaNumberList(i + 2) & "' lng='" & paradaNumberList(i + 3) _
        '                          & "' n ='" & paradaNumberList(i + 1) & " " & paradaTxtList(indexFound + 1) & "'/>"
    
        k = 0
        'search the layer of the parada:
        For Each LayerName In LayersName
            If LayerName = paradaNumberList(i) Then
                Exit For
            End If
            k = k + 1
        Next
       
        'Is the layer of the parada has been opened?
        LayerOpened = False
        If indiceOfOpenedLayers(0) <> -1 Then
            For Each indice In indiceOfOpenedLayers
                If indice = "" Then
                    Exit For
                ElseIf indice = k Then
                    LayerOpened = True
                    Exit For
                End If
            Next
        End If
        
        'If not, write the tag of paradas:
        If LayerOpened = False Then
            XmlLayers(k) = XmlLayers(k) & "<S>"
            ReDim Preserve indiceOfOpenedLayers(indiceOfindiceOfOpenedLayers)
            indiceOfOpenedLayers(indiceOfindiceOfOpenedLayers) = k
            indiceOfindiceOfOpenedLayers = indiceOfindiceOfOpenedLayers + 1
        End If
        
        'write the bus stop in the corresponding Layer:
        XmlLayers(k) = XmlLayers(k) & paradaNumberList(i + 1)
    
        
        
    Next
    
    'write the end tag of paradas:
    If indiceOfOpenedLayers(0) <> -1 Then
     For Each indice In indiceOfOpenedLayers
        XmlLayers(indice) = XmlLayers(indice) & "</S>"
     Next
    End If
    'write all the layers in the file:
    For Each Layer In XmlLayers
        If Layer = "" Then
            Exit For
        End If
        xmlFile.WriteLine (Layer & "</L>")
    Next
    
    'write end root tag
    xmlFile.WriteLine ("</ROOT>")
    
    'close the file
    xmlFile.Close
    
'        Dim polytest As Object
'        Dim polytype As Integer
        
'        Set polytest = sset.Item(0)
'        polytype = polytest.Type
    
'    Dim Msg, Style, Title, Response
'    Msg = "x1 = "
'    Msg2 = "lat1 = " & CVar(coord(1, 0)) & " lng1 = " & CVar(coord(1, 1))
'    Msg3 = "x2 = " & CVar(coord(2, 0)) & " y2 = " & CVar(coord(2, 1))
'    Msg4 = "lat2 = " & CVar(coord(3, 0)) & " lng2 = " & CVar(coord(3, 1))
'    Title = "MsgBox coucou"
'    Response = MsgBox(Msg1 & Msg2 & Msg3 & Msg4, vbInformation + vbDefaultButton1, Title)
    
    
    

End Sub

Function GetCoordinatesReferences()
    'create selection set to find geographicals coordinates references:
    'if the selection set "Text" exists delete it otherwise move on
    Dim ssetTxt As AcadSelectionSet
    On Error Resume Next
    ThisDrawing.SelectionSets.Item("Text").Delete
    
    Set ssetTxt = ThisDrawing.SelectionSets.Add("Text")
    'find geographicals coordinates references values in coord geo 1 layer
            Dim FilterType(0 To 1) As Integer
            Dim FilterData(0 To 1) As Variant
            FilterType(0) = 0: FilterData(0) = "TEXT"
            FilterType(1) = 8: FilterData(1) = "coord geo 1"
        ssetTxt.Select acSelectionSetAll, , , FilterType, FilterData
    
    'Msg in case there is not layers with references coordinates:
    Dim MsgBoxTxt
    MsgBoxTxt1 = "the layer coord geo "
    MsgBoxTxt2 = "doesn't exit. " _
            & "It has to be created with the center of a circle " _
            & "at a know coordinate point and a text with the " _
            & "geographical point under this form : xxxx.xxx;xxxx.xxx " _
            & "the first number has latitude and th second has longitude"

    'Show a msgbox if the coord geo 1 layer does not exist
    If ssetTxt.Count <> 1 Then
            MsgBox (MsgBoxTxt1 & "1 " & MsgBoxTxt2)
            End
    End If
        
        'record coordinates values:
        latlng1Txt = Split(ssetTxt.Item(0).TextString, ";")
        
        'convert coordinates to number:
        Dim latlng1(0 To 2) As Double
        latlng1(0) = CDbl(latlng1Txt(0))
        latlng1(1) = CDbl(latlng1Txt(1))
        
    'find geographicals coordinates references values in coord geo 2 layer
            FilterType(1) = 8: FilterData(1) = "coord geo 2"
        ssetTxt.Select acSelectionSetAll, , , FilterType, FilterData
        
    'Show a msgbox if the coord geo 2 layer does not exist
    If ssetTxt.Count <> 2 Then
            MsgBox (MsgBoxTxt1 & "2 " & MsgBoxTxt2)
            End
    End If
        
        'record coordinates values:
        latlng2Txt = Split(ssetTxt.Item(1).TextString, ";")
        
        sseTxt.Delete
        
        'convert coordinates to number:
        Dim latlng2(0 To 2) As Double
        latlng2(0) = CDbl(latlng2Txt(0))
        latlng2(1) = CDbl(latlng2Txt(1))

    'create selection set to find corresponding (x;y) values of the autocad file:
    'if the selection set "XY" exists delete it otherwise move on
    On Error Resume Next
    ThisDrawing.SelectionSets.Item("XY").Delete
    
    Set ssetXY = ThisDrawing.SelectionSets.Add("XY")
    
    'find corresponding (x;y) values of the autocad file:
    'for the layer coord geo 1:
            FilterType(0) = 0: FilterData(0) = "CIRCLE"
            FilterType(1) = 8: FilterData(1) = "coord geo 1"
        ssetXY.Select acSelectionSetAll, , , FilterType, FilterData

        'record coordinates values:
        xyz1 = ssetXY.Item(0).Center
    
    'for the layer coord geo 2:
            FilterType(0) = 0: FilterData(0) = "CIRCLE"
            FilterType(1) = 8: FilterData(1) = "coord geo 2"
        ssetXY.Select acSelectionSetAll, , , FilterType, FilterData

        'record coordinates values:
        xyz2 = ssetXY.Item(1).Center
        
    'create array to return all these informations:
    Dim coord(3, 1) As Double
    coord(0, 0) = latlng1(0)
    coord(0, 1) = latlng1(1)
    coord(1, 0) = xyz1(0)
    coord(1, 1) = xyz1(1)
    coord(2, 0) = latlng2(0)
    coord(2, 1) = latlng2(1)
    
    coord(3, 0) = xyz2(0)
    coord(3, 1) = xyz2(1)
    
    GetCoordinatesReferences = coord

End Function
Function GetGeoTransformation(coord)
    Dim lat1 As Double
    Dim lng1 As Double
    Dim x1 As Double
    Dim y1 As Double
    Dim lat2 As Double
    Dim lng2 As Double
    Dim x2 As Double
    Dim y2 As Double
    lat1 = coord(0, 0)
    lng1 = coord(0, 1)
    x1 = coord(1, 0)
    y1 = coord(1, 1)
    lat2 = coord(2, 0)
    lng2 = coord(2, 1)
    x2 = coord(3, 0)
    y2 = coord(3, 1)

    'point2 is calculate in new planes with point1 as the center:
    x2 = x2 - x1
    y2 = y2 - y1
    
    lat2 = lat2 - lat1
    lng2 = lng2 - lng1
    
    'to polars coordinates:
    'Dim coordPol(1) As Double
    'Dim coordPolGeo(1) As Double
    
    coordPol = cartesianToPolar(x2, y2)
    coordPolGeo = cartesianToPolar(lng2, lat2)
   
    coef = coordPolGeo(0) / coordPol(0)
    
    rot = coordPolGeo(1) - coordPol(1)
    If rot < 0 Then
        rot = rot + 2 * PI
    End If

    Dim buffer(1) As Double
    buffer(0) = coef
    buffer(1) = rot
    
    GetGeoTransformation = buffer

End Function
 
 
Sub GetSelectionOnScreen() 'As AcadSelectionSet


    'extract the polylines to add as busses lines:
    Dim ssetPoly As AcadSelectionSet
    On Error Resume Next
    ThisDrawing.SelectionSets.Item("Polylines").Delete
    
    Set ssetPoly = ThisDrawing.SelectionSets.Add("Polylines")
    'select the polylines:
            Dim FilterType(0 To 1) As Integer
            Dim FilterData(0 To 1) As Variant
            FilterType(0) = 0: FilterData(0) = "POLYLINE,LWPOLYLINE"
        ssetPoly.SelectOnScreen 'FilterType, FilterData
    

    
        'GetSelectionOnScreen = ThisDrawing.SelectionSets.Item("Polylines")
End Sub
Function getLayerRgb(Item)
    Dim LayerName As String
    Dim objLayer As AcadLayer
    Dim color As AcadAcCmColor
    Dim rgb As String
    
    LayerName = Item.Layer
    Set objLayer = ThisDrawing.Layers.Item(LayerName)
    Set color = objLayer.TrueColor

    'data from http://www.isctex.com/acadcolors.php

    Select Case color.ColorIndex
        Case 0
            rgb = 0
        Case 1
            rgb = "FF0000"
        Case 2
            rgb = "FFFF00"
        Case 3
            rgb = "00FF00"
        Case 4
            rgb = "00FFFF"
        Case 5
            rgb = "0000FF"
        Case 6
            rgb = "FF00FF"
        Case 7
            rgb = "FFFFFF"
        Case 8
            rgb = "414141"
        Case 9
            rgb = "808080"
        Case 10
            rgb = "FF0000"
        Case 11
            rgb = "FFAAAA"
        Case 12
            rgb = "BD0000"
        Case 13
            rgb = "BD7E7E"
        Case 14
            rgb = "810000"
        Case 15
            rgb = "815656"
        Case 16
            rgb = "680000"
        Case 17
            rgb = "684545"
        Case 18
            rgb = "4F0000"
        Case 19
            rgb = "4F3535"
        Case 20
            rgb = "FF3F00"
        Case 21
            rgb = "FFBFAA"
        Case 22
            rgb = "BD2E00"
        Case 23
            rgb = "BD8D7E"
        Case 24
            rgb = "811F0"
        Case 25
            rgb = "816056"
        Case 26
            rgb = "68190"
        Case 27
            rgb = "684E45"
        Case 28
            rgb = "4F1300"
        Case 29
            rgb = "4F3B35"
        Case 30
            rgb = "FF7F00"
        Case 31
            rgb = "FFD4AA"
        Case 32
            rgb = "BD5E00"
        Case 33
            rgb = "BD9D7E"
        Case 34
            rgb = "814000"
        Case 35
            rgb = "816B56"
        Case 36
            rgb = "683400"
        Case 37
            rgb = "685645"
        Case 38
            rgb = "4F2700"
        Case 39
            rgb = "4F4235"
        Case 40
            rgb = "FFBF00"
        Case 41
            rgb = "FFEAAA"
        Case 42
            rgb = "BD8D00"
        Case 43
            rgb = "BDAD7E"
        Case 44
            rgb = "816000"
        Case 45
            rgb = "817556"
        Case 46
            rgb = "684E00"
        Case 47
            rgb = "685F45"
        Case 48
            rgb = "4F3B00"
        Case 49
            rgb = "4F4935"
        Case 50
            rgb = "FFFF00"
        Case 51
            rgb = "FFFFAA"
        Case 52
            rgb = "BDBD00"
        Case 53
            rgb = "BDBD7E"
        Case 54
            rgb = "818100"
        Case 55
            rgb = "818156"
        Case 56
            rgb = "686800"
        Case 57
            rgb = "686845"
        Case 58
            rgb = "4F4F00"
        Case 59
            rgb = "4F4F35"
        Case 60
            rgb = "BFFF00"
        Case 61
            rgb = "EAFFAA"
        Case 62
            rgb = "8DBD00"
        Case 63
            rgb = "ADBD7E"
        Case 64
            rgb = "608100"
        Case 65
            rgb = "768156"
        Case 66
            rgb = "4E6800"
        Case 67
            rgb = "5F6845"
        Case 68
            rgb = "3B4F00"
        Case 69
            rgb = "494F35"
        Case 70
            rgb = "7FFF00"
        Case 71
            rgb = "D4FFAA"
        Case 72
            rgb = "5EBD00"
        Case 73
            rgb = "9DBD7E"
        Case 74
            rgb = "408100"
        Case 75
            rgb = "6B8156"
        Case 76
            rgb = "346800"
        Case 77
            rgb = "566845"
        Case 78
            rgb = "274F00"
        Case 79
            rgb = "424F35"
        Case 80
            rgb = "3FFF00"
        Case 81
            rgb = "BFFFAA"
        Case 82
            rgb = "2EBD00"
        Case 83
            rgb = "8DBD7E"
        Case 84
            rgb = "1F8100"
        Case 85
            rgb = "608156"
        Case 86
            rgb = "196800"
        Case 87
            rgb = "4E6845"
        Case 88
            rgb = "134F00"
        Case 89
            rgb = "3B4F35"
        Case 90
            rgb = "00FF00"
        Case 91
            rgb = "AAFFAA"
        Case 92
            rgb = "00BD00"
        Case 93
            rgb = "7EBD7E"
        Case 94
            rgb = "008100"
        Case 95
            rgb = "568156"
        Case 96
            rgb = "006800"
        Case 97
            rgb = "456845"
        Case 98
            rgb = "004F00"
        Case 99
            rgb = "354F35"
        Case 100
            rgb = "00FF3F"
        Case 101
            rgb = "AAFFBF"
        Case 102
            rgb = "00BD2E"
        Case 103
            rgb = "7EBD8D"
        Case 104
            rgb = "00811F"
        Case 105
            rgb = "568160"
        Case 106
            rgb = "006819"
        Case 107
            rgb = "45684E"
        Case 108
            rgb = "004F13"
        Case 109
            rgb = "354F3B"
        Case 110
            rgb = "00FF7F"
        Case 111
            rgb = "AAFFD4"
        Case 112
            rgb = "00BD5E"
        Case 113
            rgb = "7EBD9D"
        Case 114
            rgb = "008140"
        Case 115
            rgb = "56816b"
        Case 116
            rgb = "006834"
        Case 117
            rgb = "456856"
        Case 118
            rgb = "004f27"
        Case 119
            rgb = "354f42"
        Case 120
            rgb = "00ffbf"
        Case 121
            rgb = "aaffea"
        Case 122
            rgb = "00bd8d"
        Case 123
            rgb = "7ebdad"
        Case 124
            rgb = "008160"
        Case 125
            rgb = "568176"
        Case 126
            rgb = "00684e"
        Case 127
            rgb = "45685f"
        Case 128
            rgb = "004f3b"
        Case 129
            rgb = "354f49"
        Case 130
            rgb = "00ffff"
        Case 131
            rgb = "aaffff"
        Case 132
            rgb = "00bdbd"
        Case 133
            rgb = "7ebdbd"
        Case 134
            rgb = "008181"
        Case 135
            rgb = "568181"
        Case 136
            rgb = "006868"
        Case 137
            rgb = "456868"
        Case 138
            rgb = "004f4f"
        Case 139
            rgb = "354f4f"
        Case 140
            rgb = "00bfff"
        Case 141
            rgb = "aaeaff"
        Case 142
            rgb = "008dbd"
        Case 143
            rgb = "7eadbd"
        Case 144
            rgb = "006081"
        Case 145
            rgb = "567681"
        Case 146
            rgb = "004e68"
        Case 147
            rgb = "455f68"
        Case 148
            rgb = "003b4f"
        Case 149
            rgb = "35494f"
        Case 150
            rgb = "007fff"
        Case 151
            rgb = "aad4ff"
        Case 152
            rgb = "005ebd"
        Case 153
            rgb = "7e9dbd"
        Case 154
            rgb = "004081"
        Case 155
            rgb = "566b81"
        Case 156
            rgb = "003468"
        Case 157
            rgb = "455668"
        Case 158
            rgb = "00274f"
        Case 159
            rgb = "35424f"
        Case 160
            rgb = "003fff"
        Case 161
            rgb = "aabfff"
        Case 162
            rgb = "002ebd"
        Case 163
            rgb = "7e8dbd"
        Case 164
            rgb = "001f81"
        Case 165
            rgb = "566081"
        Case 166
            rgb = "001968"
        Case 167
            rgb = "454e68"
        Case 168
            rgb = "00134f"
        Case 169
            rgb = "353b4f"
        Case 170
            rgb = "0000ff"
        Case 171
            rgb = "aaaaff"
        Case 172
            rgb = "0000bd"
        Case 173
            rgb = "7e7ebd"
        Case 174
            rgb = "000081"
        Case 175
            rgb = "565681"
        Case 176
            rgb = "000068"
        Case 177
            rgb = "454568"
        Case 178
            rgb = "00004f"
        Case 179
            rgb = "35354f"
        Case 180
            rgb = "3f00ff"
        Case 181
            rgb = "bfaaff"
        Case 182
            rgb = "2e00bd"
        Case 183
            rgb = "8d7ebd"
        Case 184
            rgb = "1f0081"
        Case 185
            rgb = "605681"
        Case 186
            rgb = "190068"
        Case 187
            rgb = "4e4568"
        Case 188
            rgb = "13004f"
        Case 189
            rgb = "3b354f"
        Case 190
            rgb = "7f00ff"
        Case 191
            rgb = "d4aaff"
        Case 192
            rgb = "5e00bd"
        Case 193
            rgb = "9d7ebd"
        Case 194
            rgb = "400081"
        Case 195
            rgb = "6b5681"
        Case 196
            rgb = "340068"
        Case 197
            rgb = "564568"
        Case 198
            rgb = "27004f"
        Case 199
            rgb = "42354f"
        Case 200
            rgb = "bf00ff"
        Case 201
            rgb = "eeaaff"
        Case 202
            rgb = "8d00bd"
        Case 203
            rgb = "ad7ebd"
        Case 204
            rgb = "600081"
        Case 205
            rgb = "765681"
        Case 206
            rgb = "4e0068"
        Case 207
            rgb = "5f4568"
        Case 208
            rgb = "3b004f"
        Case 209
            rgb = "49354f"
        Case 210
            rgb = "ff00ff"
        Case 211
            rgb = "ffaaff"
        Case 212
            rgb = "bd00bd"
        Case 213
            rgb = "bd7ebd"
        Case 214
            rgb = "810081"
        Case 215
            rgb = "815681"
        Case 216
            rgb = "680068"
        Case 217
            rgb = "684568"
        Case 218
            rgb = "4f004f"
        Case 219
            rgb = "4f354f"
        Case 220
            rgb = "ff00bf"
        Case 221
            rgb = "ffaaea"
        Case 222
            rgb = "bd008d"
        Case 223
            rgb = "bd7ead"
        Case 224
            rgb = "810060"
        Case 225
            rgb = "815676"
        Case 226
            rgb = "68004e"
        Case 227
            rgb = "68455f"
        Case 228
            rgb = "4f003b"
        Case 229
            rgb = "4f3549"
        Case 230
            rgb = "ff007f"
        Case 231
            rgb = "ffaad4"
        Case 232
            rgb = "bd005e"
        Case 233
            rgb = "bd7e9d"
        Case 234
            rgb = "810040"
        Case 235
            rgb = "81566b"
        Case 236
            rgb = "680034"
        Case 237
            rgb = "684556"
        Case 238
            rgb = "4f002"
        Case 239
            rgb = "4f3542"
        Case 240
            rgb = "ff003f"
        Case 241
            rgb = "ffaabf"
        Case 242
            rgb = "bd002e"
        Case 243
            rgb = "bd7e8d"
        Case 244
            rgb = "81001f"
        Case 245
            rgb = "815660"
        Case 246
            rgb = "680019"
        Case 247
            rgb = "68454e"
        Case 248
            rgb = "4f0013"
        Case 249
            rgb = "4f353b"
        Case 250
            rgb = "333333"
        Case 251
            rgb = "505050"
        Case 252
            rgb = "696969"
        Case 253
            rgb = "828282"
        Case 254
            rgb = "bebebe"
        Case 255
            rgb = "ffffff"
    End Select

    getLayerRgb = rgb
            
End Function
Function cartesianToPolar(x As Double, y As Double)
                    'transformation to polar coordinates (r, alpha):
                    Dim r As Double
                    Dim alpha As Double
                    Const PI = 3.14159265358979
                    
                    r = Sqr(x * x + y * y)
                    
                    'calcul of alpha in the range [0;2pi[
                    If x > 0 Then
                        If y >= 0 Then
                            alpha = Atn(y / x)
                        End If
                        If y < 0 Then
                            alpha = Atn(y / x)
                            alpha = alpha + 2 * PI
                        End If
                    ElseIf x < 0 Then
                        alpha = Atn(y / x)
                        alpha = alpha + PI
                    ElseIf x = 0 Then
                        If y > 0 Then
                            alpha = PI / 2
                        ElseIf y < 0 Then
                            alpha = -PI / 2
                        End If
                    Else
                        'ERROR
                    End If
                    
    Dim buffer(1) As Double
    buffer(0) = r
    buffer(1) = alpha
    
    cartesianToPolar = buffer
End Function
